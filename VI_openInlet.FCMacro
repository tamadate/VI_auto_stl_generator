### This code generate virtual impactor geometroy with "stl" extention
### First version was created Apr/1/2023 || Final editing May/2/2023
### Edited by Dr. Tomoya Tamadate || University of Minnesota 
### Tested with Linux Mint 20.3 Cinnamon and FreeCAD 0.20.1

## You can set all parameters here (see ...)
import math
import numpy as np
W=0.35 #0.014*25.4
jetDistance=W*1.5 							# 2W
inletRadius=2
inletAngle=20/180.0*math.pi				#30deg
nozzleRadius=W*0.5						# 0.5W
curveInletNozzle=nozzleRadius	
nozzleLength=nozzleRadius*5				# 5W
openRadius=50
inletRound=0.5

## working directory
dir="/home/tama3rdgen/git/VI_auto_stl_generator/" 	# !!!!!!!!!!!!!!!!!! This section is nessesarry to change to fit your environment !!!!!!!!!!!!!!!!!!
saveAs=dir+"testDesign.FCStd"			# file name

## Open and save as ~/CFD_sub_projects/newDesign/testDesign.FCStd
exec(open('/usr/share/freecad/Mod/Start/StartPage/LoadNew.py').read())	# !!!!!!!!!!!!!!!!!! This section is nessesarry to change to fit your environment !!!!!!!!!!!!!!!!!!
App.setActiveDocument("Unnamed")
App.ActiveDocument=App.getDocument("Unnamed")
App.getDocument("Unnamed").saveAs(saveAs) 

### Preparation of sketching (set plane)
Gui.activateWorkbench("PartDesignWorkbench")
App.activeDocument().addObject('PartDesign::Body','Body')
Gui.activateView('Gui::View3DInventor', True)
Gui.activeView().setActiveObject('pdbody', App.activeDocument().Body)
App.activeDocument().Body.newObject('Sketcher::SketchObject','Sketch')
App.activeDocument().Sketch.Support = (App.activeDocument().XY_Plane, [''])
App.activeDocument().Sketch.MapMode = 'FlatFace'
App.ActiveDocument.recompute()
Gui.activeDocument().setEdit('Sketch')
Gui.activateWorkbench('SketcherWorkbench')
import PartDesignGui

#----------------------------------------------------Draw sketching-----------------------------------------------------------------------------------------------#
faceName=[]

#inlet round
r0=App.Vector(inletRadius,0,0)
center=r0+App.Vector(inletRound*math.cos(inletAngle),-inletRound*math.sin(inletAngle),0)
App.ActiveDocument.Sketch.addGeometry(Part.ArcOfCircle(Part.Circle(center,App.Vector(0,0,1),inletRound),math.pi*0.5,math.pi-inletAngle),False)
faceName.append("inletRound")

#inlet conversion
r0=App.Vector(inletRadius,0,0)
r1=App.Vector(0,0,0)
r1[0]=(1-math.cos(inletAngle))*curveInletNozzle+nozzleRadius
r1[1]-=(r0[0]-r1[0])/math.tan(inletAngle)
App.ActiveDocument.Sketch.addGeometry(Part.LineSegment(r0,r1),False)
r0=App.Vector(r1[0],r1[1],r1[2])
faceName.append("conversion")

#inlet conversion to nozzle curve
r1[0]=nozzleRadius
r1[1]=r0[1]-math.sin(inletAngle)*curveInletNozzle
center=r1+App.Vector(curveInletNozzle,0,0)
App.ActiveDocument.Sketch.addGeometry(Part.ArcOfCircle(Part.Circle(center,App.Vector(0,0,1),curveInletNozzle),math.pi-inletAngle,math.pi),False)
r0=App.Vector(r1[0],r1[1],r1[2])
faceName.append("conv_to_nozzle")

#nozzle
r1=r0-App.Vector(0,nozzleLength,0)
App.ActiveDocument.Sketch.addGeometry(Part.LineSegment(r0,r1),False)
r0=App.Vector(r1[0],r1[1],r1[2])
faceName.append("nozzle")

#nozzle outlet
r1=r0-App.Vector(nozzleRadius,0,0)
App.ActiveDocument.Sketch.addGeometry(Part.LineSegment(r0,r1),False)
r0=App.Vector(r1[0],r1[1],r1[2])
faceName.append("nozzleOutlet")

#axis
offset=inletRound*(1-math.sin(inletAngle))
r1=App.Vector(0,openRadius+offset,0)
App.ActiveDocument.Sketch.addGeometry(Part.LineSegment(r0,r1),False)
r0=App.Vector(r1[0],r1[1],r1[2])
faceName.append("axis")

#inlet
center=App.Vector(0,offset,0)
App.ActiveDocument.Sketch.addGeometry(Part.ArcOfCircle(Part.Circle(center,App.Vector(0,0,1),openRadius),0,math.pi*0.5),False)
r0=App.Vector(openRadius,offset,0)
faceName.append("inlet")

#inlet wall
r1=App.Vector(inletRadius,0,0)
r1=r1+App.Vector(inletRound*math.cos(inletAngle),offset,0)
App.ActiveDocument.Sketch.addGeometry(Part.LineSegment(r0,r1),False)
r0=App.Vector(r1[0],r1[1],r1[2])
faceName.append("inletWall")

Gui.activateWorkbench('PartDesignWorkbench')
App.getDocument('Unnamed').recompute()
Gui.getDocument("Unnamed").getObject("Sketch").Visibility=True
nface=len(faceName)

print("Sketching done!!!!!!!!!!!!!!")
#----------------------------------------------------Draw sketching done-----------------------------------------------------------------------------------------------#



#----------------------------------------------------Extrude sketch-----------------------------------------------------------------------------------------------#
Gui.activateWorkbench("PartWorkbench") # change mode to part
# extrude
f = FreeCAD.getDocument('Unnamed').addObject('Part::Extrusion', 'Extrude')
f = App.getDocument('Unnamed').getObject('Extrude')
f.Base = App.getDocument('Unnamed').getObject('Sketch')
f.DirMode = "Normal"
f.DirLink = None
f.LengthFwd = 0.1	# thickness
f.LengthRev = 0
f.Solid = True
f.Reversed = False
f.Symmetric = False
f.TaperAngle = 0
f.TaperAngleRev = 0
Gui.ActiveDocument.Extrude.ShapeColor=Gui.ActiveDocument.Sketch.ShapeColor
Gui.ActiveDocument.Extrude.LineColor=Gui.ActiveDocument.Sketch.LineColor
Gui.ActiveDocument.Extrude.PointColor=Gui.ActiveDocument.Sketch.PointColor
f.Base.ViewObject.hide()
App.ActiveDocument.recompute()
print("Extrude done!!!!!!!!!!!!!!")
#----------------------------------------------------Extrude sketch done-----------------------------------------------------------------------------------------------#


#----------------------------------------------------Down-grade-----------------------------------------------------------------------------------------------#
### Down-grade part body -> solid
Gui.Selection.clearSelection()
Gui.Selection.addSelection('Unnamed','Extrude')
Gui.activateWorkbench("DraftWorkbench")
Gui.runCommand('Draft_Downgrade',0)
_objs_ = Draft.downgrade(FreeCADGui.Selection.getSelection(), delete=True)
FreeCAD.ActiveDocument.recompute()
### Down-grade part solid -> surface
Gui.Selection.clearSelection()
Gui.Selection.addSelection('Unnamed','Solid')
Gui.activateWorkbench("DraftWorkbench")
Gui.runCommand('Draft_Downgrade',0)
_objs_ = Draft.downgrade(FreeCADGui.Selection.getSelection(), delete=True)
FreeCAD.ActiveDocument.recompute()
print("Down grade done!!!!!!!!!!!!!!")
#----------------------------------------------------Down-grade done-----------------------------------------------------------------------------------------------#



#----------------------------------------------------Mesh generation-----------------------------------------------------------------------------------------------#
import MeshPartGui, FreeCADGui
import Mesh, Part, PartGui
import MeshPart
Gui.Selection.clearSelection()
Gui.activateWorkbench("MeshWorkbench")
Gui.Selection.addSelection('Unnamed','Face','Face1',3.1981,-4.50908,0.1)
FreeCADGui.runCommand('MeshPart_Mesher')

__doc__=FreeCAD.getDocument("Unnamed")
__mesh__=__doc__.addObject("Mesh::Feature","Mesh")
__part__=__doc__.getObject("Face")
__shape__=Part.getShape(__part__,"Face1")
__mesh__.Mesh=MeshPart.meshFromShape(Shape=__shape__, LinearDeflection=0.1, AngularDeflection=0.523599, Relative=False)
__mesh__.Label="Mesh"
del __doc__, __mesh__, __part__, __shape__

Gui.Selection.clearSelection()
Gui.Selection.addSelection('Unnamed','Mesh')

for i in np.arange(1,nface):
	Gui.Selection.clearSelection()
	Gui.activateWorkbench("MeshWorkbench")
	Gui.Selection.addSelection('Unnamed','Face'+"{0:03}".format(i),'Face1',3.1981,-4.50908,0.1)
	FreeCADGui.runCommand('MeshPart_Mesher')

	__doc__=FreeCAD.getDocument("Unnamed")
	__mesh__=__doc__.addObject("Mesh::Feature","Mesh")
	__part__=__doc__.getObject("Face"+"{0:03}".format(i))
	__shape__=Part.getShape(__part__,"Face1")
	__mesh__.Mesh=MeshPart.meshFromShape(Shape=__shape__, LinearDeflection=0.1, AngularDeflection=0.523599, Relative=False)
	__mesh__.Label="Mesh"+"{0:03}".format(i)
	del __doc__, __mesh__, __part__, __shape__

	Gui.Selection.clearSelection()
	Gui.Selection.addSelection('Unnamed','Mesh')

print("Meshing done!!!!!!!!!!!!!!")
#----------------------------------------------------Mesh generation done-----------------------------------------------------------------------------------------------#



#----------------------------------------------------Export mesh as .ast file-----------------------------------------------------------------------------------------------#
FreeCAD.ActiveDocument.recompute()
Gui.Selection.addSelection('Unnamed','Mesh')
print(dir+str(0)+'.ast')
Mesh.export(FreeCADGui.Selection.getSelection(), dir+str(0)+'.ast')

for i in np.arange(1,nface):
	Gui.Selection.clearSelection()
	Gui.Selection.addSelection('Unnamed','Mesh'+"{0:03}".format(i))
	Mesh.export(FreeCADGui.Selection.getSelection(), dir+str(i)+'.ast')

### Combine & edit .ast files
import os
for i in np.arange(nface):
	os.system("sed -i 's/Mesh/"+faceName[i]+"/' "+dir+str(i)+".ast")

### Combine ast files
os.system("rm "+dir+"VI.stl")
os.system("cat "+dir+"*ast >> "+dir+"VI.stl")
os.system("rm "+dir+"*ast")


#---------------------------------------------------------------------------------------------------------------------------------------------------#
fout=open(dir+"OpenFOAM/system/meshDict","w")
with open(dir+"Base/meshDict") as f:
    lines = [line.rstrip('\n') for line in f]
    for line in lines:
        print(line)
        if(line=="###"):
            fout.write("{\n\tnewPatchNames\n\t{\n")
            for fn in faceName:
                ty="wall"
                if(fn=="inlet" or fn=="majorOutlet" or fn=="majorOutlet"):
                      ty="patch"
                if(fn=="axis"):
                      ty="symmetryPlane"
                fout.write("\t\t"+fn+"\n\t\t{\n\t\t\tnewName "+fn+";\n\t\t\ttype "+ty+";\n\t\t}\n")
            fout.write("\t}\n}")
        else:
            fout.write(line+"\n")
fout.close()
